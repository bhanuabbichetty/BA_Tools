(defun gr-p (p m) (list (+ (* (car m) (car p)) (* (caddr m) (cadr p)) (nth 4 m)) (+ (* (cadr m) (car p)) (* (nth 3 m) (cadr p)) (nth 5 m))))
(defun gr-m (m p sx sy r / c s q) (setq c (cos r) s (sin r) q (gr-p p m)) (list (+ (* (car m) c sx) (* (caddr m) s sx)) (+ (* (cadr m) c sx) (* (nth 3 m) s sx)) (+ (* (car m) (- s) sy) (* (caddr m) c sy)) (+ (* (cadr m) (- s) sy) (* (nth 3 m) c sy)) (car q) (cadr q)))
(defun gr-xy (p) (strcat (rtos (car p) 2 12) "\t" (rtos (cadr p) 2 12)))
(defun gr-row (s) (write-line s gr-file))
(defun gr-walk (e m layer depth / d typ lay p q name block b base bm pts v tx)
 (while (and e (< depth 25))
  (setq d (entget e) typ (cdr (assoc 0 d)) lay (cdr (assoc 8 d)))
  (if (= lay "0") (setq lay layer))
  (cond
   ((= typ "INSERT")
    (setq name (cdr (assoc 2 d)) block (tblsearch "BLOCK" name))
    (if block
     (progn
      (setq base (cdr (assoc 10 block)) bm (gr-m m (cdr (assoc 10 d)) (cond ((cdr (assoc 41 d))) (1.0)) (cond ((cdr (assoc 42 d))) (1.0)) (cond ((cdr (assoc 50 d))) (0.0))))
      (setq bm (append (list (car bm) (cadr bm) (caddr bm) (nth 3 bm)) (list (- (nth 4 bm) (+ (* (car bm) (car base)) (* (caddr bm) (cadr base)))) (- (nth 5 bm) (+ (* (cadr bm) (car base)) (* (nth 3 bm) (cadr base)))))))
      (gr-walk (cdr (assoc -2 block)) bm lay (1+ depth)))))
   ((= typ "CIRCLE") (gr-row (strcat "C\t" lay "\t" (gr-xy (gr-p (cdr (assoc 10 d)) m)) "\t" (rtos (* (cdr (assoc 40 d)) (sqrt (+ (* (car m) (car m)) (* (cadr m) (cadr m))))) 2 12))))
   ((member typ '("ARC" "ELLIPSE" "SPLINE")) (gr-row (strcat "U\t" lay "\tUnsupported curved edge")))
   ((= typ "LINE")
    (setq p (gr-p (cdr (assoc 10 d)) m) q (gr-p (cdr (assoc 11 d)) m))
    (gr-row (strcat "L\t" lay "\t" (gr-xy p) "\t" (gr-xy q))))
   ((= typ "LWPOLYLINE")
    (setq pts nil)
    (foreach v d (if (= (car v) 10) (setq pts (append pts (list (gr-p (cdr v) m))))))
    (if (= 1 (logand 1 (cdr (assoc 70 d)))) (setq pts (append pts (list (car pts)))))
    (foreach v d (if (and (= (car v) 42) (> (abs (cdr v)) 0.000001)) (gr-row (strcat "U\t" lay "\tCurved polyline"))))
    (while (cdr pts) (gr-row (strcat "L\t" lay "\t" (gr-xy (car pts)) "\t" (gr-xy (cadr pts)))) (setq pts (cdr pts))))
   ((member typ '("TEXT" "MTEXT" "ATTRIB"))
    (setq tx "")
    (foreach v d (if (member (car v) '(1 3)) (setq tx (strcat tx (cdr v)))))
    (setq tx (vl-string-translate "\t\n\r" "   " tx) p (gr-p (cdr (assoc 10 d)) m))
    (gr-row (strcat "T\t" lay "\t" (gr-xy p) "\t" tx)))
   ((= typ "ENDBLK") (setq e nil)))
  (if e (setq e (entnext e)))))
(defun c:GRREAD (/ gr-file)
 (setq gr-file (open (getenv "GRID_READER_OUTPUT") "w" "utf8"))
 (gr-walk (entnext) '(1.0 0.0 0.0 1.0 0.0 0.0) "0" 0)
 (write-line "DONE" gr-file) (close gr-file)
 (princ "GRID_READ_COMPLETE") (princ))
